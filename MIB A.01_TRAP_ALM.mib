Emcore-Optiva-ALM-TRAP DEFINITIONS ::= BEGIN

IMPORTS
		MODULE-IDENTITY,
        OBJECT-TYPE,
		NOTIFICATION-TYPE,
        TimeTicks
                FROM SNMPv2-SMI
        DisplayString
                FROM SNMPv2-TC
        optivaNMS, emcore
                FROM Emcore-SMI;

emcore-optiva-ALM-TRAP MODULE-IDENTITY
        LAST-UPDATED "201009200000Z"
        ORGANIZATION "Emcore Corp"
        CONTACT-INFO
         "www.emcore.com
          Postal: 2015 Chestnut St.
                  Alhambra, CA 91803
                  USA
          Tel: +1 (626) 293-3400"
        DESCRIPTION
              "This MIB describes the protocol for monitoring & controlling
              the Emcore-Optiva System.  The NMS SNMP Agent Card provides
              the primary interface. Other associated MIBs may provide more 
              specific detail or extra functionality for certain card types.
              
              Some Network Management programs may require a zero '0' be
              added to the end of the address for specific OIDs.
              (SNMP version 1.)"
        REVISION	"201009200000Z"
        DESCRIPTION 
          "SNMP version 1"
        ::= { optivaNMS 100 }

------------------------------------------
-- File Number: FW-tbd
-- File Description: MIB, Optiva Alarm Trap
-- File Revision Letter: A-draft 
------------------------------------------


emcoreOptivaTrap OBJECT IDENTIFIER ::= { emcore-optiva-ALM-TRAP 1 }  

slotIndex NOTIFICATION-TYPE   
	STATUS current
	--ENTERPRISE snmp
	--OBJECTS { optivaChassis }
	DESCRIPTION "Show where the device located"
    ::= { emcoreOptivaTrap 1 }           

summeryAlarm NOTIFICATION-TYPE  
	STATUS current
	--ENTERPRISE snmp
	--OBJECTS { optivaChassis }
    DESCRIPTION
         "0 = Empty     No card present and not part of Baseline.
          1 = OK        No alarms to report from this specific card.
          2 = Warning   No major alarms.  Minor alarm status may exist
          3 = Alarm     Major failure indicated by this card.
          4 = Fault-Missing     This card is missing or non-responsive.
                    Applies only if card is part of Baseline configuration
                    and CardMissingEnabled is enabled."
     ::= { emcoreOptivaTrap 2 }            
	
cardType NOTIFICATION-TYPE 
	STATUS current
	--ENTERPRISE snmp
	--OBJECTS { optivaChassis }
    DESCRIPTION "Show device card."
	::= { emcoreOptivaTrap 3 }

END
