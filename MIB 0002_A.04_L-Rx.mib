Emcore-Optiva-L-RX DEFINITIONS ::= BEGIN

IMPORTS
        MODULE-IDENTITY,
        OBJECT-TYPE,
        NOTIFICATION-TYPE,
        TimeTicks
                FROM SNMPv2-SMI
        DisplayString
                FROM SNMPv2-TC
        optivaNMS, emcore
                FROM Emcore-SMI;

emcore-optiva-L-RX MODULE-IDENTITY
        LAST-UPDATED "201208270000Z"
        ORGANIZATION "Emcore Corp"
        CONTACT-INFO
         "Emcore Broadband Division
          www.emcore.com

          Postal: 2015 Chestnut St.
                  Alhambra, CA 91803
                  USA

          Tel: +1 (626) 293-3400"

        DESCRIPTION
                "Emcore-Optiva System"
        REVISION	"201208220000Z"
        DESCRIPTION 
          "OptivaView NMS"
        ::= { optivaNMS 1 }

------------------------------------------
-- File Number: MIB-0002
-- File Description: MIB, Optiva L Rx
-- File Version: A.04
------------------------------------------

optivaLRxObjects OBJECT IDENTIFIER ::= { emcore-optiva-L-RX 4 }


moduleTemp OBJECT-TYPE
        SYNTAX     INTEGER (-4500..12500)
        MAX-ACCESS read-only
        STATUS     current
        DESCRIPTION
                "Unit 100C, 2500 = 25.0 C"
        ::= { optivaLRxObjects 1 }



relativeRFgainSetting OBJECT-TYPE
        SYNTAX     DisplayString (SIZE (4))
        MAX-ACCESS read-write
        STATUS     current
        DESCRIPTION
                 "Command to increase or decrease RF Gain:
                 1= increases aprox.  1 dB
                 0= decreases approx. 1 dB 
                 Read Output:
                 0 corresponds to maximum RF gain.  
                 -30 corresponds to approx. 30 dB less than max gain. 
                 Software value may be greater than hardware limit
				 Valid Range = -30 to 0"
        ::= { optivaLRxObjects 2}
        

rfPowerOut OBJECT-TYPE
        SYNTAX     INTEGER (-5000..2000)
        MAX-ACCESS read-only
        STATUS     current
        DESCRIPTION
                "RF Power presented to output RF connector.
                 unit 0.01 dBm, 1000 = 10.0 dBm
                 This reading is a sampled representation"
        ::= { optivaLRxObjects 3}


pdiPower OBJECT-TYPE
        SYNTAX     INTEGER (0..5000)
        MAX-ACCESS read-only
        STATUS     current
        DESCRIPTION
                "Photo Diode Power.
                 unit 0.01 dBmo, 200 = 2 dBmo"
        ::= { optivaLRxObjects 4}


summaryAlarm OBJECT-TYPE
        SYNTAX     INTEGER (0..1)
        MAX-ACCESS read-only
        STATUS     current
        DESCRIPTION
                "1 = Alarm
                 0 = No Alarm"
        ::= { optivaLRxObjects 5}


psAlarm OBJECT-TYPE
        SYNTAX     INTEGER (0..12)
        MAX-ACCESS read-only
        STATUS     current
        DESCRIPTION 
                "Power Supply Alarm. Status of highest Voltage PS.
                 0 = No alarm (status OK)
                 1 or 3 = Major High, indicates significantly high
                 2 = Hi      
                 8 = Lo 
                 4 or 12 = Major Low, indicates significantly low
		"
       ::= { optivaLRxObjects 6}


pdiAlarm OBJECT-TYPE
        SYNTAX     INTEGER (0..12)
        MAX-ACCESS read-only
        STATUS     current
        DESCRIPTION
                "Alarm for photodiode current
                 0 = No alarm (status OK)
                 1 or 3 = Major High indicates significantly high
                 2 = Hi 
                 8 = Lo   
                 4 or 12 = Major Low indicates significantly low
                          "
        ::= { optivaLRxObjects 7}


modelNumber OBJECT-TYPE
        SYNTAX     DisplayString (SIZE (32))
        MAX-ACCESS read-only
        STATUS     current
        DESCRIPTION
                "Model Number"
        ::= { optivaLRxObjects 8}


serialNumber OBJECT-TYPE
        SYNTAX     DisplayString (SIZE (8))
        MAX-ACCESS read-only
        STATUS     current
        DESCRIPTION
                "Serial Number"
        ::= { optivaLRxObjects 9}


manufacturingDate OBJECT-TYPE
        SYNTAX     DisplayString (SIZE (8))
        MAX-ACCESS read-only
        STATUS     current
        DESCRIPTION
                "Manufacturing Date"
        ::= { optivaLRxObjects 10}


firmwareRev OBJECT-TYPE
        SYNTAX     DisplayString (SIZE (4))
        MAX-ACCESS read-only
        STATUS     current
        DESCRIPTION
                "Firmware Revision"
        ::= { optivaLRxObjects 11}

hardwareRev OBJECT-TYPE
        SYNTAX     DisplayString (SIZE (4))
        MAX-ACCESS read-only
        STATUS     current
        DESCRIPTION
                "Hardware Revision"
        ::= { optivaLRxObjects 12}

rfPwrOutalarmMajLo OBJECT-TYPE
        SYNTAX     DisplayString (SIZE (5))
        MAX-ACCESS read-write
        STATUS     current
        DESCRIPTION "RF Power Out that triggers Major Low Alarm.
                 0 = 0 dBm  
                 -100 =  -10 dBm
                 Units = 0.1 dBm
                 Valid Range = -300 to 800
                 This software range is wider than hardware can
                 achieve.
                 This value has been factory set at -20dBm
                 Deviation from factory setting is not advised"
        ::= { optivaLRxObjects 13}

rfPwrOutalarmMnrLo OBJECT-TYPE
        SYNTAX     DisplayString (SIZE (5))
        MAX-ACCESS read-write
        STATUS     current
        DESCRIPTION "RF Power Out that triggers Minor Low Alarm.
                 0 = 0 dBm  
                 -100 =  -10 dBm
                 Units = 0.1 dBm
                 Valid Range = -300 to 800
                 This software range is wider than hardware can
                 achieve. 
                 This value has been factory set at -10dBm
                 Deviation from factory setting is not advised"
        ::= { optivaLRxObjects 14}


rfPwrOutalarmMnrHigh OBJECT-TYPE
        SYNTAX     DisplayString (SIZE (5))
        MAX-ACCESS read-write
        STATUS     current
        DESCRIPTION
                "RF Power Out that triggers Minor High Alarm.
                 0 = 0 dBm  
                 -100 =  -10 dBm
                 Units = 0.1 dBm
                 Valid Range = -300 to 800
                 This software range is wider than hardware can
                 achieve.
                 This value has been factory set at +8dBm
                 Deviation from factory setting is not advised"
        ::= { optivaLRxObjects 15}


rfPwrOutalarmMajHigh OBJECT-TYPE
        SYNTAX     DisplayString (SIZE (5))
        MAX-ACCESS read-write
        STATUS     current
        DESCRIPTION
                "RF Power Out that triggers Major High Alarm.
                 0 = 0 dBm  
                 -100 =  -10 dBm
                 Units = 0.1 dBm
                 Valid Range = -300 to 800
                 This software range is wider than hardware can
                 achieve.
                 This value has been factory set at +10dBm
                 Deviation from factory setting is not advised"
        ::= { optivaLRxObjects 16}

rfAlarmEnable OBJECT-TYPE
        SYNTAX     INTEGER {
        					disable (0),
        					enable (1)
        				   }
        MAX-ACCESS read-write
        STATUS     current
        DESCRIPTION "Disable/Enable the RF Alarm.
             		0 = Disable RF Alarm
             		1 = Enable RF Alarm"
		::= { optivaLRxObjects 17}

END
