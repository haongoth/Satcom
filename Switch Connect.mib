Emcore-Optiva-Switch DEFINITIONS ::= BEGIN

IMPORTS
        MODULE-IDENTITY,
        OBJECT-TYPE,  
		Unsigned32 
		       FROM SNMPv2-SMI
        NOTIFICATION-TYPE, 
        TimeTicks
                FROM SNMPv2-SMI
        DisplayString
                FROM SNMPv2-TC
        TRAP-TYPE
		FROM RFC-1215
        optivaNMS, emcore
                FROM Emcore-SMI;

optivaNMS MODULE-IDENTITY
        LAST-UPDATED "201303270000Z"
        ORGANIZATION "Emcore Corp"
        CONTACT-INFO
          "www.emcore.com
           Postal: 2015 Chestnut St.
                   Alhambra, CA 91803
                   USA
           Tel: +1 (626) 293-3400"
        DESCRIPTION  "This MIB defines the SNMP interface to monitor and control the 
               features of the Optical Switch Unit (OSU) for Emcore Optiva systems."
        REVISION   "A_02 04/22/2013"
        DESCRIPTION 
          "SNMP version 1"
        ::= { emcoreMgmt 1 }

emcoreOptivaSwitchTable OBJECT-TYPE     
 		SYNTAX SEQUENCE OF EmcoreOptivaSwitchEntry
        ACCESS  not-accessible
        STATUS  mandatory
        DESCRIPTION 
          "OptivaView NMS"
        ::= { optivaNMS 5 }

EmcoreOptivaSwitchEntry OBJECT-TYPE  
		SYNTAX  EmcoreOptivaSwitchEntry
        ACCESS  not-accessible
        STATUS  mandatory
        DESCRIPTION 
        	"A list of osu module general status entries."
	 	INDEX {readSlotIndex }
	 	::= { emcoreOptivaSwitchTable 1 }

EmcoreOptivaSwitchEntry ::= SEQUENCE {
        switchEnable
            INTEGER,
        manAuto
            INTEGER,
        autoType
            INTEGER,
        switchStat
            INTEGER,
        spareStat
            INTEGER,
        cardStatus
            INTEGER,
        modelNumber
            DisplayString,
        serialNumber
            DisplayString,
        manufacturingDate
            DisplayString,
        firmwareRev
            DisplayString,
        hardwareRev
            DisplayString,
		switchNumbers
		    INTEGER,	
		selectSwitch
		    INTEGER,
		switchSpoolDelay 
		    Unsigned32,
		activeTotalDelay 
		    Unsigned32,
		switchSpoolLoss 
		    INTEGER,
		activeTotalLoss 
		    INTEGER,
	}


switchEnable OBJECT-TYPE
        SYNTAX     INTEGER {
        					rsuNormal (0),
        					rsuSpare (1),
        					osuBypass (2),
        					osuDelay (3)
        					}
        MAX-ACCESS read-write
        STATUS     current
        DESCRIPTION "The present switch enable of the RSU or OSU.
                     Read or write switch enable information to active switch number.
		     If the command is writen to this address, the RSU or OSU will move
                     to that switch position only if the present control state and 
                     alarm inputs allow it.
                     0 = rsuNormal 
                     1 = rsuSpare
                     2 = osuBypass 
                     3 = osuDelay"
        ::= { emcoreOptivaSwitchEntry 1 }



manAuto OBJECT-TYPE
        SYNTAX     INTEGER {
        					manual (0),
        					auto (1),
        					noSupport(2)
        					}
        MAX-ACCESS read-write
        STATUS     current
        DESCRIPTION "The control mode of the RSU or OSU.
             		0 = manual
             		1 = automatic
                 	2 =	no support"
       ::= { emcoreOptivaSwitchEntry  2}
        
autoType OBJECT-TYPE
        SYNTAX     INTEGER {
        					auto-Dual(0),
        					single-Revert (1),
        					single-Latch (2),
						    noSupport (3)
        					}
        MAX-ACCESS read-only
        STATUS     obsolete
        DESCRIPTION
                "Does not working for OSU or RSU.
		Control Mode: 	auto-Dual = 0
                		single-Revert = 1
                		single-Latch = 2
                		no support = 3"
        ::= { emcoreOptivaSwitchEntry 3}

switchStat OBJECT-TYPE
        SYNTAX     INTEGER (0..512)
        MAX-ACCESS read-only
        STATUS     current
        DESCRIPTION "Read active switch input status as received by the RSU or OSU.
             		0 = oK
             		1 = alarm #1
             		2 = alarm #2
             		4 = alarm #3
             		8 = alarm #4
             		alarm 1 | 2 | 4 | 8"
        ::= { emcoreOptivaSwitchEntry 4 }

spareStat OBJECT-TYPE
        SYNTAX     INTEGER {
        					oK (0),
        					aLARM (1),
						    noSupport (2)
        					}
        MAX-ACCESS read-only
        STATUS     current
        DESCRIPTION "Does not support by OSU
		     		Position B or spare card status as received by the RSU.
                    The last 2 digits of the name are the slot number.
             		0 = oK
             		1 = alarm
                	2 = no support"
        ::= { emcoreOptivaSwitchEntry 5 }


cardStatus OBJECT-TYPE
        SYNTAX     INTEGER {
        					oK (0),
         					aLARM (1)
        					}
        MAX-ACCESS read-only
        STATUS     current
        DESCRIPTION "Alarm Status for the OSU or RSU itself.
                     The last 2 digits of the name are the slot number.
             		0 = oK
             		1 = alarm (major failure condition requiring immediate attention)"
        ::= { emcoreOptivaSwitchEntry 6 }

modelNumber OBJECT-TYPE
        SYNTAX     DisplayString (SIZE (32))
        MAX-ACCESS read-only
        STATUS     current
        DESCRIPTION
                "Model Number"
        ::= { emcoreOptivaSwitchEntry 8}


serialNumber OBJECT-TYPE
        SYNTAX     DisplayString (SIZE (8))
        MAX-ACCESS read-only
        STATUS     current
        DESCRIPTION
                "Serial Number"
        ::= { emcoreOptivaSwitchEntry 9}


manufacturingDate OBJECT-TYPE
        SYNTAX     DisplayString (SIZE (8))
        MAX-ACCESS read-only
        STATUS     current
        DESCRIPTION
                "Manufacturing Date"
        ::= { emcoreOptivaSwitchEntry 10}


firmwareRev OBJECT-TYPE
        SYNTAX     DisplayString (SIZE (4))
        MAX-ACCESS read-only
        STATUS     current
        DESCRIPTION
                "Firmware Revision"
        ::= { emcoreOptivaSwitchEntry 11}

hardwareRev OBJECT-TYPE
        SYNTAX     DisplayString (SIZE (4))
        MAX-ACCESS read-only
        STATUS     current
        DESCRIPTION
                "Hardware Revision"
        ::= { emcoreOptivaSwitchEntry 12}

switchNumbers OBJECT-TYPE
        SYNTAX     INTEGER (1..8)
        MAX-ACCESS read-only
        STATUS     current
        DESCRIPTION "The total switch numbers of the OSU or RSU.
                     read the total osu switch numbers at this address"
        ::= { emcoreOptivaSwitchEntry 13 }

selectSwitch OBJECT-TYPE
        SYNTAX     INTEGER (1..8)
        MAX-ACCESS read-write
        STATUS     current
        DESCRIPTION "The select switch of the OSU or RSU.
                     write current active switch number to this address"
        ::= { emcoreOptivaSwitchEntry 14 }

switchSpoolDelay OBJECT-TYPE
        SYNTAX     Unsigned32 
        MAX-ACCESS read-write
        STATUS     current
        DESCRIPTION "The switch spool delay of the OSU.
                     write or read current active switch spool delay to this address "
         ::= { emcoreOptivaSwitchEntry 15 }


activeTotalDelay OBJECT-TYPE
        SYNTAX     Unsigned32 
        MAX-ACCESS read-only
        STATUS     current
        DESCRIPTION "Total spool delay at current switchs status of the OSU
		     Read active total spool delay at this address."
        ::= { emcoreOptivaSwitchEntry 16 }

switchSpoolLoss OBJECT-TYPE
        SYNTAX     INTEGER 
        MAX-ACCESS read-write
        STATUS     current
        DESCRIPTION "The switch spool loss of the OSU.
                     write or read current active switch spool loss, 
                     loss value times 100 to this address "
         ::= { emcoreOptivaSwitchEntry 17 }


activeTotalLoss OBJECT-TYPE
        SYNTAX     INTEGER 
        MAX-ACCESS read-only
        STATUS     current
        DESCRIPTION "Total spool loss at current switchs status of the OSU
		     Read active total spool loss at this address."
        ::= { emcoreOptivaSwitchEntry 18 }


END
