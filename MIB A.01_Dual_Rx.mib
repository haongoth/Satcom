Emcore-Optiva-Dual-Rx DEFINITIONS ::= BEGIN

IMPORTS
        MODULE-IDENTITY,
        OBJECT-TYPE,
        NOTIFICATION-TYPE,
        TimeTicks
                FROM SNMPv2-SMI
        DisplayString
                FROM SNMPv2-TC
        TRAP-TYPE
		FROM RFC-1215
        optivaNMS, emcore
                FROM Emcore-SMI;

optivaNMS MODULE-IDENTITY
        LAST-UPDATED "201511250000Z"
        ORGANIZATION "Emcore Corp"
        CONTACT-INFO
          "www.emcore.com
           Postal: 2015 Chestnut St.
                   Alhambra, CA 91803
                   USA
           Tel: +1 (626) 293-3400"
        DESCRIPTION  "This MIB defines the SNMP interface to monitor and control the 
               features of the LBand Dual Rx for Emcore Optiva systems."
        REVISION   "201511250000Z"
        
        DESCRIPTION 
          "SNMP version 1"
        ::= { emcoreMgmt 1 }

emcoreOptivaDualRxTable OBJECT-TYPE     
 		SYNTAX SEQUENCE OF EmcoreOptivaDualRxEntry
        ACCESS  not-accessible
        STATUS  mandatory
        DESCRIPTION 
          "EmcoreView NMS"
        ::= { optivaNMS 7 }

emcoreOptivaDualRxEntry OBJECT-TYPE  
		SYNTAX  EmcoreOptivaDualRxEntry
        ACCESS  not-accessible
        STATUS  mandatory
        DESCRIPTION 
        	"A list of Dual Rx module general status entries."
	 	INDEX {readSlotIndex }
	 	::= { emcoreOptivaDualRxTable 1 }

EmcoreOptivaDualRxEntry ::= SEQUENCE {
        moduleTemp 
            INTEGER,
        relativeRFgainSetting 
            INTEGER,
        rfPowerOut 
            INTEGER,
        pdiCurrent 
            INTEGER,
        summaryAlarm 
            INTEGER,
        psAlarm 
            INTEGER,
        pdiAlarm 
            INTEGER,
        modelNumber
            DisplayString,
        serialNumber
            DisplayString,
        manufacturingDate
            DisplayString,
        firmwareRev
            DisplayString,
        hardwareRev
            DisplayString,
		rfPwrAtLsrRFalarmMajLo
	        DisplayString,
		rfPwrAtLsrRFalarmMnrLo
	        DisplayString,
		rfPwrAtLsrRFalarmMnrHigh
		    DisplayString,
		rfPwrAtLsrRFalarmMajHigh
		    DisplayString,
	}

moduleTemp OBJECT-TYPE
        SYNTAX     INTEGER (-4500..12500)
        MAX-ACCESS read-only
        STATUS     current
        DESCRIPTION
                "Unit 100C, 2500 = 25.0 C"
        ::= { emcoreOptivaDualRxEntry 1 }



relativeRFgainSetting OBJECT-TYPE
        SYNTAX     INTEGER (0..3175)
        MAX-ACCESS read-write
        STATUS     current
        DESCRIPTION
                 "Command to increase or decrease RF Gain
        		      0 corresponds to maximum RF gain.  
                 	  3175 corresponds to approx. 31.75 dB less than max gain.
                      Units = 0.01 dB"
        ::= { emcoreOptivaDualRxEntry 2}
        

rfPowerOut OBJECT-TYPE
        SYNTAX     INTEGER (-5000..2000)
        MAX-ACCESS read-only
        STATUS     current
        DESCRIPTION
                "RF Power presented to output RF connector.
                 unit 0.01 dBm, 1000 = 10.0 dBm
                 This reading is a sampled representation"
        ::= { emcoreOptivaDualRxEntry 3}


pdiCurrent OBJECT-TYPE
        SYNTAX     INTEGER (0..5000)
        MAX-ACCESS read-only
        STATUS     current
        DESCRIPTION
                "Photo Diode Current.
                 unit 0.01 mA, 200 = 2 mA"
        ::= { emcoreOptivaDualRxEntry 4}


summaryAlarm OBJECT-TYPE
        SYNTAX     INTEGER {
        					oK (0),
        					alarm (1)
                           }
        MAX-ACCESS read-only
        STATUS     current
        DESCRIPTION
                "1 = Alarm
                 0 = No Alarm"
        ::= { emcoreOptivaDualRxEntry 5}


psAlarm OBJECT-TYPE
        SYNTAX     INTEGER {
        					oK (0),
        					majorHi (1),
        					warningHi (2),
        					warningLo (4),
        					majorLo (8)
        					}
        MAX-ACCESS read-only
        STATUS     current
        DESCRIPTION 
                "Power Supply Alarm. Status of highest Voltage PS.
                 0 = No alarm (status OK)
                 1 = Major High, indicates significantly high
                 2 = Hi      
                 4 = Lo 
                 8 = Major Low, indicates significantly low
				"
       ::= { emcoreOptivaDualRxEntry 6}


pdiAlarm OBJECT-TYPE
        SYNTAX     INTEGER {
        					oK (0),
        					majorHi (1),
        					warningHi (2),
        					majorLo (4)
        					warningLo (8),
        					}
        MAX-ACCESS read-only
        STATUS     current
        DESCRIPTION
                "Alarm for photodiode current
                 0 = No alarm (status OK)
                 1 = Major High indicates significantly high
                 2 = Hi 
                 4 = Major Low indicates significantly low
                 8 = Warn Low                  "
        ::= { emcoreOptivaDualRxEntry 7}


modelNumber OBJECT-TYPE
        SYNTAX     DisplayString (SIZE (32))
        MAX-ACCESS read-only
        STATUS     current
        DESCRIPTION
                "Model Number"
        ::= { emcoreOptivaDualRxEntry 8}


serialNumber OBJECT-TYPE
        SYNTAX     DisplayString (SIZE (8))
        MAX-ACCESS read-only
        STATUS     current
        DESCRIPTION
                "Serial Number"
        ::= { emcoreOptivaDualRxEntry 9}


manufacturingDate OBJECT-TYPE
        SYNTAX     DisplayString (SIZE (8))
        MAX-ACCESS read-only
        STATUS     current
        DESCRIPTION
                "Manufacturing Date"
        ::= { emcoreOptivaDualRxEntry 10}


firmwareRev OBJECT-TYPE
        SYNTAX     DisplayString (SIZE (4))
        MAX-ACCESS read-only
        STATUS     current
        DESCRIPTION
                "Firmware Revision"
        ::= { emcoreOptivaDualRxEntry 11}

hardwareRev OBJECT-TYPE
        SYNTAX     DisplayString (SIZE (4))
        MAX-ACCESS read-only
        STATUS     current
        DESCRIPTION
                "Hardware Revision"
        ::= { emcoreOptivaDualRxEntry 12}

rfPwrAtLsrRFalarmMajLo OBJECT-TYPE
        SYNTAX     DisplayString (SIZE (5))
        MAX-ACCESS read-write
        STATUS     current
        DESCRIPTION "RF Power at Laser that triggers Major Low Alarm.
                 0 = 0 dBm  
                 -100 =  -10 dBm
                 Units = 0.1 dBm
                 Valid Range = -200 to 300
                 This software range is wider than hardware can
                 achieve.
                 This value has been factory set at -20dBm
                 Deviation from factory setting is not advised"
        ::= { emcoreOptivaDualRxEntry 13}

rfPwrAtLsrRFalarmMnrLo OBJECT-TYPE
        SYNTAX     DisplayString (SIZE (5))
        MAX-ACCESS read-write
        STATUS     current
        DESCRIPTION "RF Power at Laser that triggers Minor Low Alarm.
                 0 = 0 dBm  
                 -100 =  -10 dBm
                 Units = 0.1 dBm
                 Valid Range = -200 to 300
                 This software range is wider than hardware can
                 achieve. 
                 This value has been factory set at -6dBm
                 Deviation from factory setting is not advised"
        ::= { emcoreOptivaDualRxEntry 14}


rfPwrAtLsrRFalarmMnrHigh OBJECT-TYPE
        SYNTAX     DisplayString (SIZE (5))
        MAX-ACCESS read-write
        STATUS     current
        DESCRIPTION
                "RF Power at Laser that triggers Minor High Alarm.
                 0 = 0 dBm  
                 -100 =  -10 dBm
                 Units = 0.1 dBm
                 Valid Range = -200 to 300
                 This software range is wider than hardware can
                 achieve.
                 This value has been factory set at +6dBm
                 Deviation from factory setting is not advised"
        ::= { emcoreOptivaDualRxEntry 15}


rfPwrAtLsrRFalarmMajHigh OBJECT-TYPE
        SYNTAX     DisplayString (SIZE (5))
        MAX-ACCESS read-write
        STATUS     current
        DESCRIPTION
                "RF Power at Laser that triggers Major High Alarm.
                 0 = 0 dBm  
                 -100 =  -10 dBm
                 Units = 0.1 dBm
                 Valid Range = -200 to 300
                 This software range is wider than hardware can
                 achieve.
                 This value has been factory set at +10dBm
                 Deviation from factory setting is not advised"
        ::= { emcoreOptivaDualRxEntry 16}

END
